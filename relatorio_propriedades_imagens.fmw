FME workspace relatorio_propriedades_imagens.fmw

Parameters:
- SourceDataset_GEOTIFF =   # Arquivos Geotiff
- DestDataset_CSV =   # Pasta para gravação do CSV
- FEATURE_TYPES =

Readers:
- GEOTIFF_1: GEOTIFF from $(SourceDataset_GEOTIFF)

Writers:
- CSV_1: CSV to $(DestDataset_CSV)

Note: Workspace desenvolvida pelo 1º Centro de Geoinformação com a finalidade de realizar o controle de qualidade de imagens digitais de alta resolução parte do Projeto de Mapeamento do Estado do Rio Grande do Sul
Note: Autor: / Cap Diogo Oliveira / Cap Diniz / 1º Centro de Geoinformação / Diretoria de Serviço Geográfico / Exército Brasileiro
Note: Leitor de Geotiff
GEOTIFF (reader GEOTIFF_1)
    -> AttributeExposer
File1 (writer CSV_1)
    attributes: imagem auto, lote auto, B_caminho auto, G_caminho auto, R_caminho auto, NIR_caminho auto, PAN_caminho auto, RGB_caminho auto, B_pixel_x auto, G_pixel_x auto, R_pixel_x auto, NIR_pixel_x auto, PAN_pixel_x auto, RGB_pixel_x auto, B_pixel_y auto, G_pixel_y auto, R_pixel_y auto, NIR_pixel_y auto, PAN_pixel_y auto, RGB_pixel_y auto, B_band_bit_depth auto, G_band_bit_depth auto, R_band_bit_depth auto, NIR_band_bit_depth auto, PAN_band_bit_depth auto, RGB_band0_bit_depth auto, RGB_band1_bit_depth auto, RGB_band2_bit_depth auto, RGB_band0_interpretation auto, RGB_band1_interpretation auto,
      RGB_band2_interpretation auto, B_numbands auto, G_numbands auto, R_numbands auto, NIR_numbands auto, PAN_numbands auto, RGB_numbands auto

Bookmark: Attribute
AttributeExposer
    ATTR_LIST = fme_dataset
    -> AttributeSplitter
AttributeSplitter
    ATTR_NAME = fme_dataset
    DELIMITER = \
    DROP_EMPTY_PARTS = No
    LIST_NAME = _list
    TRIM_OPTION = Both
    -> ListIndexer
ListIndexer
    INDEX = -2
    LIST_ATTR = _list{}
    PREFIX = f
    -> AttributeSplitter_2
AttributeSplitter_2
    ATTR_NAME = f_list
    DELIMITER = _
    DROP_EMPTY_PARTS = No
    LIST_NAME = _list2
    TRIM_OPTION = Both
    -> ListIndexer_2
ListIndexer_2
    INDEX = 0
    LIST_ATTR = _list2{}
    PREFIX = f
    -> ListIndexer_3
ListIndexer_3
    INDEX = -5
    LIST_ATTR = _list{}
    PREFIX = l
    -> AttributeRenamer
AttributeRenamer
    ATTR_LIST = f_list2,fanaout,,fme_basename,imagem,,fme_dataset,caminho,,l_list,lote,
    -> AttributeTrimmer
AttributeTrimmer
    SRC_ATTRS = fanaout
    TRIM_TO_NONE = Yes
    TRIM_TYPE = Both
    -> AttributeRemover_2
AttributeRemover_2
    LIST_ATTRS = _list{} _list2{}
    REMOVE_ATTRS = f_list
    -> RasterPropertyExtractor

Bookmark: Image Properties
RasterPropertyExtractor
    -> RasterBandPropertyExtractor

Bookmark: Band Properties
RasterBandPropertyExtractor
    -> AttributeManager

Bookmark: Separando Img Probelma
AttributeManager
    ATTR_TABLE:
      RENAME_SET_VALUE _num_bands > num_bands
      REMOVE _num_rows
      REMOVE _num_columns
      RENAME_SET_VALUE _spacing_x > spacing_x
      RENAME_SET_VALUE _spacing_y > spacing_y
      REMOVE _origin_x
      REMOVE _origin_y
      REMOVE _rotation_x
      REMOVE _rotation_y
      REMOVE _min_x
      REMOVE _min_y
      REMOVE _max_x
      REMOVE _max_y
      REMOVE _cell_origin_x
      REMOVE _cell_origin_y
      REMOVE _upper_left_x
      REMOVE _upper_left_y
      REMOVE _upper_right_x
      REMOVE _upper_right_y
      REMOVE _lower_right_x
      REMOVE _lower_right_y
      REMOVE _lower_left_x
      REMOVE _lower_left_y
      REMOVE _band{}.band_name
      REMOVE _band{}.band_num_tile_rows
      REMOVE _band{}.band_num_tile_columns
      REMOVE _band{}.band_nodata
      REMOVE _band{}.band_selected
      REMOVE _band{}.band_num_palettes
      REMOVE _band{}.palette{}.palette_name
      REMOVE _band{}.palette{}.palette_key_interpretation
      REMOVE _band{}.palette{}.palette_value_interpretation
      REMOVE _band{}.palette{}.palette_bit_depth
      REMOVE _band{}.palette{}.palette_selected
      RENAME_SET_VALUE _band{0}.band_interpretation > band0_band_interpretation
      RENAME_SET_VALUE _band{1}.band_interpretation > band1_band_interpretation
      RENAME_SET_VALUE _band{2}.band_interpretation > band2_band_interpretation
      RENAME_SET_VALUE _band{0}.band_bit_depth > band0_band_bit_depth
      RENAME_SET_VALUE _band{1}.band_bit_depth > band1_band_bit_depth
      RENAME_SET_VALUE _band{2}.band_bit_depth > band2_band_bit_depth
      REMOVE _band{}.band_interpretation
      REMOVE _band{}.band_bit_depth
    -> ListBuilder_2
ListBuilder_2
    GRP_BY = imagem lote
    LIST_NAME = _list
    -> ListSorter
ListSorter
    ORDER = Ascending
    SRC_LIST = _list{}.fanaout
    TYPE = Alphabetic
    -> AttributeManager_2
AttributeManager_2
    ATTR_TABLE:
      REMOVE _list{}.imagem
      REMOVE _list{}.fme_feature_type
      SET_TO B_caminho = @Value(_list{0}.caminho)
      SET_TO G_caminho = @Value(_list{1}.caminho)
      SET_TO R_caminho = @Value(_list{4}.caminho)
      SET_TO NIR_caminho = @Value(_list{2}.caminho)
      SET_TO PAN_caminho = @Value(_list{3}.caminho)
      SET_TO RGB_caminho = @Value(_list{5}.caminho)
      REMOVE _list{}.caminho
      REMOVE _list{}.fanaout
      REMOVE _list{}.lote
      SET_TO B_pixel_x = @Value(_list{0}.spacing_x)
      SET_TO G_pixel_x = @Value(_list{1}.spacing_x)
      SET_TO R_pixel_x = @Value(_list{4}.spacing_x)
      SET_TO NIR_pixel_x = @Value(_list{2}.spacing_x)
      SET_TO PAN_pixel_x = @Value(_list{3}.spacing_x)
      SET_TO RGB_pixel_x = @Value(_list{5}.spacing_x)
      REMOVE _list{}.spacing_x
      SET_TO B_pixel_y = @Value(_list{0}.spacing_y)
      SET_TO G_pixel_y = @Value(_list{1}.spacing_y)
      SET_TO R_pixel_y = @Value(_list{4}.spacing_y)
      SET_TO NIR_pixel_y = @Value(_list{2}.spacing_y)
      SET_TO PAN_pixel_y = @Value(_list{3}.spacing_y)
      SET_TO RGB_pixel_y = @Value(_list{5}.spacing_y)
      REMOVE _list{}.spacing_y
      SET_TO B_band_bit_depth = @Value(_list{0}.band0_band_bit_depth)
      SET_TO G_band_bit_depth = @Value(_list{1}.band0_band_bit_depth)
      SET_TO R_band_bit_depth = @Value(_list{4}.band0_band_bit_depth)
      SET_TO NIR_band_bit_depth = @Value(_list{2}.band0_band_bit_depth)
      SET_TO PAN_band_bit_depth = @Value(_list{3}.band0_band_bit_depth)
      SET_TO RGB_band0_bit_depth = @Value(_list{5}.band0_band_bit_depth)
      SET_TO RGB_band1_bit_depth = @Value(_list{5}.band1_band_bit_depth)
      SET_TO RGB_band2_bit_depth = @Value(_list{5}.band2_band_bit_depth)
      SET_TO RGB_band0_interpretation = @Value(_list{5}.band0_band_interpretation)
      SET_TO RGB_band1_interpretation = @Value(_list{5}.band1_band_interpretation)
      SET_TO RGB_band2_interpretation = @Value(_list{5}.band2_band_interpretation)
      REMOVE _list{}.band0_band_bit_depth
      REMOVE _list{}.band1_band_bit_depth
      REMOVE _list{}.band2_band_bit_depth
      SET_TO B_numbands = @Value(_list{0}.num_bands)
      SET_TO G_numbands = @Value(_list{1}.num_bands)
      SET_TO R_numbands = @Value(_list{4}.num_bands)
      SET_TO NIR_numbands = @Value(_list{2}.num_bands)
      SET_TO PAN_numbands = @Value(_list{3}.num_bands)
      SET_TO RGB_numbands = @Value(_list{5}.num_bands)
      REMOVE _list{}.num_bands
      REMOVE _list{}.band0_band_interpretation
      REMOVE _list{}.band1_band_interpretation
      REMOVE _list{}.band2_band_interpretation
    -> File1 (writer CSV_1)
