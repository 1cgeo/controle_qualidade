FME workspace verificacao_qualidade_hidrografia.fmw
Title: Verificação da qualidade de vetores de hidrografia
Description: Esta ferramenta visa executar um controle de qualidade automatizado das seguintes classes previstas na ET-EDGV:
* *Trecho_Drenagem*
* *Massa_Dagua*
* *Trecho_Massa_Dagua*
* *Barragem*
* *Ilha*
* *Queda_Dagua*
Para realizar o controle de qualidade também é utilizada a classe *Curva_Nivel*.
History: 20180906,Cap Diniz,Versão inicial

Parameters:
- SourceDataset_ESRISHAPE = ""C:\Users\diniz.1CGEO\Desktop\Hidro-lote-01\1_VETORES\HID_Barragem_L.shp" "C:\Users\diniz.1CGEO\Desktop\Hidro-lote-01\1_VETORES\HID_Corredeira_A.shp" "C:\Users\diniz.1CGEO\Desktop\Hidro-lote-01\1_VETORES\HID_Corredeira_L.shp" "C:\Users\diniz.1CGEO\Desktop\Hidro-lote-01\1_VETORES\HID_Ilha_A.shp" "C:\Users\diniz.1CGEO\Desktop\Hidro-lote-01\1_VETORES\HID_Massa_Dagua.shp" "C:\Users\diniz.1CGEO\Desktop\Hidro-lote-01\1_VETORES\HID_Ponto_Drenagem_P.shp" "C:\Users\diniz.1CGEO\Desktop\Hidro-lote-01\1_VETORES\HID_Queda_Dagua_P.shp" "C:\Users\diniz.1CGEO\Desktop\Hidro-lote-01\1_VETORES\HID_Trecho_Drenagem_L.shp" "C:\Users\diniz.1CGEO\Desktop\Hidro-lote-01\1_VETORES\HID_Trecho_Massa_Dagua_A.shp""   # Shapefiles de hidrografia
- SourceDataset_ESRISHAPE_3 = C:\Users\diniz.1CGEO\Desktop\Hidro-lote-03\Lote3\HID_Corredeira_A.shp   # Shapefiles de Altimetria
- DestDataset_ESRISHAPE = C:\Users\diniz.1CGEO\Desktop\Hidro-lote-01   # Pasta de destino dos erros encontrados

Readers:
- ESRISHAPE_1: ESRISHAPE from $(SourceDataset_ESRISHAPE)
- ESRISHAPE_2: ESRISHAPE from $(SourceDataset_ESRISHAPE_3)

Writers:
- ESRISHAPE_3: ESRISHAPE to $(DestDataset_ESRISHAPE)

Counter_2
    CNT_ATTR = _count
    DOMAIN = counter
    SCOPE = Global
    START = 0
    -> TINGenerator [BREAKLINES]
    -> SpatialFilter_9 [Filter]
Note: Workspace desenvolvida pelo 1º Centro de Geoinformação com a finalidade de realizar o controle de qualidade de dados geoespaciais de altimetria e hidrografia parte do Projeto de Mapeamento do Estado do Rio Grande do Sul
Note: Autor: / Cap Diniz / 1º Centro de Geoinformação / Diretoria de Serviço Geográfico / Exército Brasileiro
TINGenerator
    GROUP_BY = _count
    TOLERANCE = 0
    TIN_EDGES -> SpatialFilter_9 [Candidate]
SpatialFilter_9
    AGGREGATE_HANDLING = Yes
    BASE_TYPE = Multiple Filters
    CURVE_BOUNDARY_RULE_PARAM = Default Rule
    PASS_CRITERIA = Pass Against One Filter
    PREDATTR = _predicate
    PREDICATES = CONTAINS
    USE_BOUNDING_BOX = No
    PASSED -> CoordinateExtractor_4
CoordinateExtractor_4
    IND = 0
    MODE = Specify Coordinate
    Z_ATTR = _z0
    -> CoordinateExtractor_5
CoordinateExtractor_5
    IND = -1
    MODE = Specify Coordinate
    Z_ATTR = _z_ultimo
    -> AttributeCreator_28
AttributeCreator_28
    ATTR_TABLE = SET_TO dz = @Evaluate(@abs(@Value(_z_ultimo)-@Value(_z0)))
    -> Tester_24
Tester_24
    BOOL_OP = OR
    TEST_CLAUSE = TEST @Value(dz) > 1.67
    PASSED -> Bufferer_8
    PASSED -> SpatialFilter_10 [Candidate]
Bufferer_8
    ANGLE = 22.5
    CAP_STYLE = Round
    CORNER_STYLE = Round
    MODE = AREA
    OFFSET = 2
    BUFFERED -> Dissolver_2
Dissolver_2
    ACCUM_INPUT_ATTRS = Use Attributes From One Feature
    CLEANING_TOLERANCE = None
    CONNECT_Z_MODE = First Wins
    DEAGGREGATE_INPUT = Yes
    LIST_ATTRS_TO_INCLUDE = _count
    LIST_NAME = list
    NO_OVRLP = No
    AREA -> ListElementCounter_3
ListElementCounter_3
    CNT_ATTR = _element_count
    LIST_NAME = list{}
    -> Tester_25
Tester_25
    BOOL_OP = OR
    TEST_CLAUSE = TEST @Value(_element_count) > 4
    PASSED -> SpatialFilter_10 [Filter]
SpatialFilter_10
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeCreator_29
AttributeCreator_29
    ATTR_TABLE:
      SET_TO observacao = Desnível incompatível entre as margens do Trecho_Massa_Dagua
      SET_TO classe = lote_1_hid_medida_4_4_2
    -> 2DForcer_2

Bookmark: Vetores de hidrografia
HID_Barragem_L (reader ESRISHAPE_1)
    attributes: Id long
    -> fix_2d_4 [2DForcer_3_Input]
    -> Deaggregator_4
    -> SpatialFilter_6 [Candidate]
    -> SpatialFilter_7 [Filter]
    -> LineOnLineOverlayer [LINE]
    -> Deaggregator
    -> CoordinateExtractor_6
HID_Ilha_A (reader ESRISHAPE_1)
    attributes: Id long, tipoilha long
    -> fix_2d_2 [2DForcer_3_Input]
    -> Deaggregator_4
    -> Deaggregator
    -> CoordinateExtractor_6
HID_Massa_Dagua (reader ESRISHAPE_1)
    attributes: Id long, tipomassa long, regime long
    -> Deaggregator_4
    -> fix_2d_3 [2DForcer_3_Input]
    -> fix_2d [2DForcer_3_Input]
    -> fix_2d_5 [2DForcer_3_Input]
    -> SpatialFilter_6 [Filter]
    -> SpatialFilter_7 [Candidate]
    -> AreaOnAreaOverlayer [AREA]
    -> CoordinateRounder_4
    -> Deaggregator
    -> GeometryValidator_3
    -> CoordinateExtractor_6
HID_Trecho_Drenagem_L (reader ESRISHAPE_1)
    attributes: Id long, coincideco long
    -> fix_2d_curva_7 [2DForcer_3_Input]
    -> fix_2d_curva_4 [2DForcer_3_Input]
    -> Tester_20
    -> Deaggregator_4
    -> fix_2d_6 [2DForcer_3_Input]
    -> fix_2d_drenagem [2DForcer_3_Input]
    -> GeometryValidator_3
    -> LineOnLineOverlayer [LINE]
    -> Deaggregator
    -> CoordinateExtractor_6
HID_Trecho_Massa_Dagua_A (reader ESRISHAPE_1)
    attributes: Id long, tipotrecho long, regime long
    -> fix_2d_curva_6 [2DForcer_3_Input]
    -> fix_2d_3 [2DForcer_3_Input]
    -> fix_2d_curva_3 [2DForcer_3_Input]
    -> Deaggregator_4
    -> fix_2d [2DForcer_3_Input]
    -> fix_2d_7 [2DForcer_3_Input]
    -> SpatialFilter_6 [Filter]
    -> fix_2d_10 [2DForcer_3_Input]
    -> SpatialFilter_7 [Candidate]
    -> AreaOnAreaOverlayer [AREA]
    -> Deaggregator
    -> Counter_2
    -> GeometryValidator_3
    -> CoordinateExtractor_6
HID_Queda_Dagua_P (reader ESRISHAPE_1)
    attributes: Id long, altura float, tipoqueda short
    -> Bufferer_2
    -> fix_2d_curva_8 [2DForcer_3_Input]
    -> Deaggregator
    -> Deaggregator_4
    -> CoordinateExtractor_6
HID_Queda_Dagua_L (reader ESRISHAPE_1)
    attributes: OBJECTID long, ELEVATION double, LAYER char(254), Shape_Leng double, altura float, tipoqueda short
    -> fix_2d_curva_2 [2DForcer_3_Input]
    -> Deaggregator
    -> Bufferer_2
    -> Deaggregator_4
    -> CoordinateExtractor_6
HID_Corredeira_A (reader ESRISHAPE_1)
    attributes: tipoilha long
    -> fix_2d_curva_5 [2DForcer_3_Input]
    -> Deaggregator
    -> Deaggregator_4
    -> fix_2d [2DForcer_3_Input]
    -> CoordinateExtractor_6
HID_Corredeira_L (reader ESRISHAPE_1)
    attributes: ELEVATION double, LAYER char(254)
    -> Deaggregator_4
    -> fix_2d [2DForcer_3_Input]
    -> Deaggregator
    -> CoordinateExtractor_6
    -> fix_2d_curva_9 [2DForcer_3_Input]

Bookmark: hid_medida_6_2_4
fix_2d_4
    Deaggregator_7_Deaggregated -> Clipper [CLIPPEE]
fix_2d_3
    Deaggregator_7_Deaggregated -> Bufferer_9
Bufferer_9
    ANGLE = 22.5
    CAP_STYLE = Round
    CORNER_STYLE = Round
    MODE = AREA
    OFFSET = -0.1
    BUFFERED -> Clipper [CLIPPER]
Clipper
    ATTR_ACCUM_MODE = Merge Clipper
    ATTR_CONFLICT_RES = Use Clippee
    BOUNDARY_CASES = Treat as Inside
    CLEANING_TOLERANCE = None
    CLIPPED_ATTR = _clipped
    CLIP_TYPE = Multiple Clippers
    CONNECT_Z_MODE = First Wins
    CREATE_AGGREGATES = Yes
    LINES_AS_SEGMENTS = No
    MEASURE_TYPE = Continuous
    MISSING_VAL_MODE = Compute
    PRESERVE_CLIPPEE_EXTENTS = No
    VAL_SOURCE = Clippee Only
    INSIDE -> Deaggregator_8
Deaggregator_8
    ATTR_ACCUM_MODE = Merge List Attributes
    ATTR_CONFLICT_RES = Use List Attribute Values
    CHILD_ID_ATTR = _hierarchy_child_id_list
    COPY_ATTR = Every Node
    EXPLODE_INSTANCES = No
    GEOM_NAME_FIELD = _geometry_name
    ID_ATTR = _hierarchy_id
    ID_SELECTION = ID and Parent ID
    LIST_ATTR_MODE_LOOKUP = LEAN
    MODE = Flatten One Level
    PARENT_ID_ATTR = _hierarchy_parent_id
    PART_NUMBER_FIELD = _part_number
    SPLIT_COMPOSITES = No
    DEAGGREGATED -> AttributeCreator_32
AttributeCreator_32
    ATTR_TABLE:
      SET_TO observacao = Traçado incorreto Barragem vs TMD/MD
      SET_TO classe = lote_1_hid_medida_6_2_4
    -> 2DForcer_2

Bookmark: hid_medida_6_2_2
fix_2d_2
    Deaggregator_7_Deaggregated -> Clipper_2 [CLIPPER]
fix_2d
    Deaggregator_7_Deaggregated -> Clipper_2 [CLIPPEE]
Clipper_2
    BOUNDARY_CASES = Treat as Inside
    CLEANING_TOLERANCE = None
    CLIPPED_ATTR = _clipped
    CLIP_TYPE = Multiple Clippers
    CREATE_AGGREGATES = No
    LINES_AS_SEGMENTS = No
    MEASURE_TYPE = Continuous
    MISSING_VAL_MODE = Compute
    PRESERVE_CLIPPEE_EXTENTS = No
    VAL_SOURCE = Clippee Only
    INSIDE -> Deaggregator_3
Deaggregator_3
    ATTR_ACCUM_MODE = Merge List Attributes
    ATTR_CONFLICT_RES = Use List Attribute Values
    CHILD_ID_ATTR = _hierarchy_child_id_list
    COPY_ATTR = Every Node
    EXPLODE_INSTANCES = No
    GEOM_NAME_FIELD = _geometry_name
    ID_ATTR = _hierarchy_id
    ID_SELECTION = ID and Parent ID
    LIST_ATTR_MODE_LOOKUP = LEAN
    MODE = Flatten One Level
    PARENT_ID_ATTR = _hierarchy_parent_id
    PART_NUMBER_FIELD = _part_number
    SPLIT_COMPOSITES = No
    DEAGGREGATED -> AreaCalculator
AreaCalculator
    AREA_ATTR = _area
    AREA_TYPE = Plane Area
    MULT = 1
    -> Tester_2
Tester_2
    BOOL_OP = OR
    TEST_CLAUSE = TEST @Value(_area) > 2
    PASSED -> AttributeCreator_4
AttributeCreator_4
    ATTR_TABLE:
      SET_TO observacao = Relacionamento espacial inválido entre Ilha e Massa_Dagua/Trecho_Massa_Dagua/Corredeira
      SET_TO classe = lote_1_hid_medida_6_2_2
    -> 2DForcer_2

Bookmark: hid_medida_4_3_3 / hid_medida_4_3_4
fix_2d_5
    Deaggregator_7_Deaggregated -> Clipper_3 [CLIPPER]
fix_2d_6
    Deaggregator_7_Deaggregated -> Clipper_3 [CLIPPEE]
    Deaggregator_7_Deaggregated -> Clipper_4 [CLIPPEE]
Clipper_3
    BOUNDARY_CASES = Treat as Inside
    CLEANING_TOLERANCE = None
    CLIPPED_ATTR = _clipped
    CLIP_TYPE = Multiple Clippers
    CREATE_AGGREGATES = Yes
    LINES_AS_SEGMENTS = No
    MEASURE_TYPE = Continuous
    MISSING_VAL_MODE = Compute
    PRESERVE_CLIPPEE_EXTENTS = No
    VAL_SOURCE = Clippee Only
    INSIDE -> Deaggregator_5
Deaggregator_5
    ATTR_ACCUM_MODE = Merge List Attributes
    ATTR_CONFLICT_RES = Use List Attribute Values
    CHILD_ID_ATTR = _hierarchy_child_id_list
    COPY_ATTR = Every Node
    EXPLODE_INSTANCES = No
    GEOM_NAME_FIELD = _geometry_name
    ID_ATTR = _hierarchy_id
    ID_SELECTION = ID and Parent ID
    LIST_ATTR_MODE_LOOKUP = LEAN
    MODE = Flatten One Level
    PARENT_ID_ATTR = _hierarchy_parent_id
    PART_NUMBER_FIELD = _part_number
    SPLIT_COMPOSITES = No
    DEAGGREGATED -> LengthCalculator_2
LengthCalculator_2
    DIM = 2
    LEN_ATTR = _length
    MULT = 1
    -> Tester_4
Tester_4
    BOOL_OP = OR
    TEST_CLAUSE = TEST @Value(_length) > 2
    PASSED -> AttributeCreator_6
AttributeCreator_6
    ATTR_TABLE:
      SET_TO observacao = Relacionamento espacial inválido entre Trecho_Drenagem e Massa_Dagua
      SET_TO classe = lote_1_hid_medida_4_3_3
    -> Junction_11
fix_2d_7
    Deaggregator_7_Deaggregated -> Counter
Counter
    CNT_ATTR = _tmd
    DOMAIN = counter
    SCOPE = Global
    START = 0
    -> Clipper_4 [CLIPPER]
    -> FeatureMerger [REQUESTOR]
Clipper_4
    ATTR_ACCUM_MODE = Merge Clipper
    ATTR_CONFLICT_RES = Use Clippee
    BOUNDARY_CASES = Treat as Inside
    CLEANING_TOLERANCE = None
    CLIPPED_ATTR = _clipped
    CLIP_TYPE = Multiple Clippers
    CREATE_AGGREGATES = No
    LINES_AS_SEGMENTS = No
    MEASURE_TYPE = Continuous
    MISSING_VAL_MODE = Compute
    PRESERVE_CLIPPEE_EXTENTS = No
    VAL_SOURCE = Clippee Only
    INSIDE -> Aggregator
Aggregator
    ACCUM_ATTRS_NAME = Use Attributes From One Feature
    AGGREGATE_TYPE = Homogeneous Collection (If Possible)
    GROUP_BY = _tmd
    MODE = Geometry - Assemble One Level
    ORDERED = No
    SEP = ,
    AGGREGATE -> LengthCalculator_3
LengthCalculator_3
    DIM = 2
    LEN_ATTR = _length
    MULT = 1
    -> Tester_5
Tester_5
    BOOL_OP = OR
    TEST_CLAUSE = TEST @Value(_length) > 2
    PASSED -> FeatureMerger [SUPPLIER]
FeatureMerger
    ATTR_ACCUM_MODE = Merge Supplier
    ATTR_CONFLICT_RES = Use Requestor
    IGNORE_NULLS = No
    JOIN_KEYS = @Value(_tmd) @Value(_tmd) AUTO
    MERGE_TYPE = Attributes Only
    PROCESS_DUPS = NO
    REJECT_NULL_MISSING_KEYS = No
    SUPPLIERS_FIRST = No
    UNMERGED_REQUESTOR -> AttributeCreator_7
AttributeCreator_7
    ATTR_TABLE:
      SET_TO observacao = Trecho_Massa_Dagua deve conter pelo menos um elemento de Trecho_Drenagem
      SET_TO classe = lote_1_hid_medida_4_3_4
    -> Junction_11
Junction_11
    -> 2DForcer_2

Bookmark: hid_medida_4_5_3
CoordinateRounder_4
    XPREC = 0
    YPREC = 0
    ZPREC = 0
    ROUNDED -> CoordinateExtractor_3
CoordinateExtractor_3
    LIST_NAME = _indices
    MODE = All Coordinates
    -> ListHistogrammer
ListHistogrammer
    LIST_NAME = _histogram
    SRC_LIST = _indices{}.z
    -> ListElementCounter
ListElementCounter
    CNT_ATTR = _element_count
    LIST_NAME = _histogram{}
    -> Tester
Tester
    BOOL_OP = OR
    TEST_CLAUSE = TEST @Value(_element_count) > 1
    PASSED -> AttributeCreator_11
AttributeCreator_11
    ATTR_TABLE:
      SET_TO observacao = Variação na coordenada Z superiores a 1 metro em Massa_Dagua
      SET_TO classe = lote_1_hid_medida_4_5_3
    -> 2DForcer_2

Bookmark: hid_medida_4_3_7 / hid_medida_4_3_8
fix_2d_curva_7
    Deaggregator_7_Deaggregated -> SpatialFilter_8 [Filter]
fix_2d_curva_4
    Deaggregator_7_Deaggregated -> SpatialFilter_4 [Filter]
fix_2d_curva_6
    Deaggregator_7_Deaggregated -> SpatialFilter_5 [Filter]
fix_2d_curva_3
    Deaggregator_7_Deaggregated -> SpatialFilter_3 [Filter]
fix_2d_curva_2
    Deaggregator_7_Deaggregated -> SpatialFilter_3 [Candidate]
SpatialFilter_3
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> fix_2d_curva_8 [2DForcer_3_Input]
    FAILED -> AttributeCreator_24
fix_2d_curva_8
    Deaggregator_7_Deaggregated -> Bufferer_6
Bufferer_6
    ANGLE = 22.5
    CAP_STYLE = Round
    CORNER_STYLE = Round
    MODE = AREA
    OFFSET = 1
    BUFFERED -> SpatialFilter_4 [Candidate]
SpatialFilter_4
    AGGREGATE_HANDLING = Yes
    BASE_TYPE = Multiple Filters
    CURVE_BOUNDARY_RULE_PARAM = Default Rule
    PASS_CRITERIA = Pass Against One Filter
    PREDATTR = _predicate
    PREDICATES = INTERSECTS
    USE_BOUNDING_BOX = No
    FAILED -> AttributeCreator_25
AttributeCreator_25
    ATTR_TABLE:
      SET_TO observacao = Queda_Dagua deve intersectar Trecho_Drenagem
      SET_TO classe = lote_1_hid_medida_4_3_7
    -> Junction
AttributeCreator_24
    ATTR_TABLE:
      SET_TO observacao = Queda_Dagua_L deve intersectar Trecho_Massa_Dagua
      SET_TO classe = lote_1_hid_medida_4_3_7
    -> Junction
fix_2d_curva_5
    Deaggregator_7_Deaggregated -> SpatialFilter_5 [Candidate]
SpatialFilter_5
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> Bufferer_7
    FAILED -> AttributeCreator_26
AttributeCreator_26
    ATTR_TABLE:
      SET_TO observacao = Corredeira_A deve intersectar Trecho_Massa_Dagua
      SET_TO classe = lote_1_hid_medida_4_3_8
    -> Junction
fix_2d_curva_9
    Deaggregator_7_Deaggregated -> Bufferer_7
Bufferer_7
    ANGLE = 22.5
    CAP_STYLE = Round
    CORNER_STYLE = Round
    MODE = AREA
    OFFSET = 1
    BUFFERED -> SpatialFilter_8 [Candidate]
SpatialFilter_8
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    FAILED -> AttributeCreator_27
AttributeCreator_27
    ATTR_TABLE:
      SET_TO observacao = Corredeira deve intersectar Trecho_Drenagem
      SET_TO classe = lote_1_hid_medida_4_3_8
    -> Junction
Junction
    -> 2DForcer_2

Bookmark: hid_medida_4_5_1
fix_2d_drenagem
    Deaggregator_7_Deaggregated -> Tester_28
Tester_28
    BOOL_OP = OR
    TEST_CLAUSE = TEST @Value(coincideco) != 11
    PASSED -> SpatialRelator_3 [Requestor]
fix_2d_curva
    Deaggregator_7_Deaggregated -> GeometryValidator_6
GeometryValidator_6
    ISSUE_ATTR_NAME = _issues
    PRESETS = All
    REPAIR = Yes
    RULES = AREA_ORIENTATION AREA_ORIENTATION]VALID]FME_CONTROLLER_QUERY_FILE]transformers\dependencies\geometryvalidator\AREA_ORIENTATION.fme CONSECUTIVE_IDENTICAL_VERTICES_2D CHECK_Z]YES]FME_CONTROLLER_QUERY_FILE]transformers\dependencies\geometryvalidator\CONSECUTIVE_IDENTICAL_VERTICES_2D.fme MISSING_TEXTURE_COORDINATES  MISSING_VERTEX_NORMALS  NAN_REMOVAL PROCESS_MEASURE]NO]FME_CONTROLLER_QUERY_FILE]transformers\dependencies\geometryvalidator\NAN_REMOVAL.fme NULL_REMOVAL  OGC_SIMPLE_CHECK  OGC_VALID_CHECK OGC_VERSION]V1.2.0]FME_CONTROLLER_QUERY_FILE]transformers\dependencies\geometryvalidator\OGC_VALID_CHECK.fme PLANAR_SURFACE CHECK_AREA]DO_NOT_CHECK_AREA]TOLERANCE_MODE]AUTO]TOLERANCE]0.0]ANGULAR_TOLERANCE_MODE]AUTO]ANGULAR_TOLERANCE]0.0]FME_CONTROLLER_QUERY_FILE]transformers\dependencies\geometryvalidator\PLANAR_SURFACE.fme SELF_INTERSECTING CHECK_HOLE_TOUCHING_POLYGON]No]CONNECT_Z_MODE_SI]FIRST_WINS]FME_CONTROLLER_QUERY_FILE]transformers\dependencies\geometryvalidator\SELF_INTERSECTING.fme SHELL_VALIDATION FLIP_APPEARANCE_MODE]FLIP_APPEARANCES]FME_CONTROLLER_QUERY_FILE]transformers\dependencies\geometryvalidator\SHELL_VALIDATION.fme SOLID_VOID_REPAIR  TYPE_REPAIR CONNECT_Z_MODE]FIRST_WINS]ARC_ENDPOINT_TOLERANCE_MODE]Auto]ARC_ENDPOINT_TOLERANCE]0.0]FME_CONTROLLER_QUERY_FILE]transformers\dependencies\geometryvalidator\TYPE_REPAIR.fme MISMATCHED_DIMENSIONS FORCE_DIMENSION]2D]FME_CONTROLLER_QUERY_FILE]transformers\dependencies\geometryvalidator\MISMATCHED_DIMENSIONS.fme MISSING_MEASURES_AND_ELEVATIONS MISSING_VALUES_MODE]SENTINEL]SENTINEL_VALUE]0]MISSING_MEASURES_MODE]CONTINUOUS]LENGTH_DIMENSION]2D]FME_CONTROLLER_QUERY_FILE]transformers\dependencies\geometryvalidator\MISSING_MEASURES_AND_ELEVATIONS.fme
    SUMMARY = Detailed
    PASSED -> SpikeRemover_2
SpikeRemover_2
    SPIKEANGLE = 1
    SPIKELENGTH = 0
    UNCHANGED -> SpatialRelator_3 [Supplier]
SpatialRelator_3
    AGGREGATE_HANDLING = Yes
    CALC_CARD = Yes
    CURVE_BOUNDARY_RULE_PARAM = Default Rule
    LIST_ATTRS_TO_INCLUDE = indice
    LIST_NAME = _relationships
    PREDICATES = INTERSECTS
    SUCCESS_ATTR = _related_candidates
    -> ListSorter
    -> ListSorter_2
ListSorter
    ORDER = Descending
    SRC_LIST = _relationships{}.card_point
    TYPE = Numeric
    -> Tester_12
Tester_12
    BOOL_OP = OR
    TEST_CLAUSE = TEST @Value(_relationships{0}.card_point) > 1
    PASSED -> AttributeCreator_18
ListSorter_2
    ORDER = Descending
    SRC_LIST = _relationships{}.card_line
    TYPE = Numeric
    -> Tester_17
Tester_17
    BOOL_OP = OR
    TEST_CLAUSE = TEST @Value(_relationships{0}.card_line) > 0
    PASSED -> AttributeCreator_18
AttributeCreator_18
    ATTR_TABLE:
      SET_TO observacao = Trecho_Drenagem cruzando mais de uma vez a mesma curva
      SET_TO classe = lote_1_hid_medida_4_5_1
    -> 2DForcer_2

Bookmark: hid_medida_4_5_2 / hid medida_4_4_1 / hid_medida_7_2_1
Tester_20
    BOOL_OP = OR
    TEST_CLAUSE = TEST @Value(coincideco) != 11
    PASSED -> CoordinateRounder
CoordinateRounder
    XPREC = 0
    YPREC = 0
    ZPREC = 2
    ROUNDED -> CoordinateExtractor
CoordinateExtractor
    LIST_NAME = _indices
    MODE = All Coordinates
    -> PythonCaller
PythonCaller
    NEW_ATTRIBUTES = dzmax xmax ymax increase{}.x increase{}.y increase{}.dz crescente distance_max
    PYTHONSOURCE:
      import fme
      import fmeobjects
      import math
      def processFeature(feature):
          l = [float(x) for x in feature.getAttribute("_indices{}.z")]
          lx = [float(x) for x in feature.getAttribute("_indices{}.x")]
          ly = [float(x) for x in feature.getAttribute("_indices{}.y")]

          crescente =  l[-1] >= l[0] + 1
          feature.setAttribute("crescente", crescente)

          if not crescente:
              dz_subida = [l[i] - l[0] for i in xrange(len(l)-1)]
              j = 0
              for i in range(len(dz_subida)):
                  if dz_subida[i] > 1.67:
                      feature.setAttribute("increase{%d}.x" % j, str(lx[i]))
                      feature.setAttribute("increase{%d}.y" % j, str(ly[i]))
                      feature.setAttribute("increase{%d}.dz" % j, str(dz_subida[i]))
                      j = j + 1

          dzl = [l[i]-l[i+1] for i in xrange(len(l)-1)]

          if len(dzl)>0:
              dz1 = max(dzl)
              dz2 = min(dzl)

              if abs(dz1) > abs(dz2):
                  dzmax = dz1
              else:
                  dzmax = dz2

              dzmax_index = dzl.index(dzmax)
              distance_max = math.sqrt((lx[dzmax_index]-lx[dzmax_index+1])**2 + (ly[dzmax_index]-ly[dzmax_index+1])**2)
              feature.setAttribute("dzmax", dzmax)
              feature.setAttribute("distance_max", distance_max)
              feature.setAttribute("xmax",lx[dzmax_index])
              feature.setAttribute("ymax", ly[dzmax_index])
    PYTHONSYMBOL = processFeature
    -> Tester_11
    -> AttributeKeeper_3
AttributeKeeper_3
    KEEP_ATTRS = distance_max,dzmax,xmax,ymax
    -> VertexCreator
VertexCreator
    MODE_NAME = Replace with Point
    XVAL = @Value(xmax)
    YVAL = @Value(ymax)
    -> Tester_9
    -> Tester_23
Tester_23
    BOOL_OP = AND
    TEST_CLAUSE = TEST @Value(dzmax) > 10
    PASSED -> SpatialFilter_2 [Filter]
Tester_9
    BOOL_OP = AND
    TEST_CLAUSE:
      TEST @Value(dzmax) > 10
      TEST @Value(distance_max) < 10
    PASSED -> SpatialFilter [Candidate]
Tester_11
    BOOL_OP = OR
    TEST_CLAUSE = TEST @Value(crescente) = Yes
    PASSED -> AttributeCreator_12
    FAILED -> AttributeKeeper_2
AttributeCreator_12
    ATTR_TABLE:
      SET_TO observacao = Trecho de drenagem sobe mais de 1,5 metros
      SET_TO classe = lote_1_hid_medida_4_5_2
    -> 2DForcer_2
AttributeKeeper_2
    KEEP_LIST = increase{}.dz increase{}.x increase{}.y
    -> ListElementCounter_2
ListElementCounter_2
    CNT_ATTR = _element_count
    LIST_NAME = increase{}
    -> Tester_8
Tester_8
    BOOL_OP = OR
    TEST_CLAUSE = TEST @Value(_element_count) > 0
    PASSED -> ListExploder
ListExploder
    ATTR_ACCUM_MODE = Merge List Attributes
    ATTR_CONFLICT_RES = Use List Attribute Values
    INDEX_ATTR = _element_index
    LIST_ATTR = increase{}
    ELEMENTS -> VertexCreator_2
VertexCreator_2
    MODE_NAME = Replace with Point
    XVAL = @Value(x)
    YVAL = @Value(y)
    -> AttributeRounder
AttributeRounder
    PLACES = 2
    ROUND_TYPE = Nearest
    SRC_ATTRS = dz
    -> AttributeCreator_5
AttributeCreator_5
    ATTR_TABLE:
      SET_TO observacao = Trecho de drenagem sobe mais de @Value(dz) metros
      SET_TO classe = lote_1_hid_medida_4_5_2
    -> 2DForcer_2
Bufferer_2
    ANGLE = 22.5
    CAP_STYLE = Round
    CORNER_STYLE = Round
    MODE = AREA
    OFFSET = 10
    BUFFERED -> SpatialFilter [Filter]
    BUFFERED -> SpatialFilter_2 [Candidate]
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeCreator_22
    FAILED -> AttributeCreator_13
AttributeCreator_22
    ATTR_TABLE = SET_TO diff_queda_dagua = @Evaluate(@abs(@Value(altura)-@Value(dzmax)))
    -> Tester_10
Tester_10
    BOOL_OP = OR
    TEST_CLAUSE = TEST @Value(diff_queda_dagua) > 1
    PASSED -> AttributeCreator_13
AttributeCreator_13
    ATTR_TABLE:
      SET_TO observacao = Trecho_Drenagem não possui o desnível correspondente ao atributo altura de Queda_Dagua
      SET_TO classe = lote_1_hid_medida_7_2_1
    -> 2DForcer_2
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    FAILED -> AttributeCreator_8
AttributeCreator_8
    ATTR_TABLE:
      SET_TO observacao = Desnível em Z superior a 10 metros sem justificativa (Queda_Dagua)
      SET_TO classe = lote_1_hid_medida_4_4_1
    -> 2DForcer_2

Bookmark: hid_medida_6_2_1 e 6_2_3
LineOnLineOverlayer
    ATTRS_ACCUM_MODE = Use Attributes From One Feature
    CLEANING_TOLERANCE = None
    DEAGGREGATE_INPUT = Yes
    GENERATE_LIST_DROP = NO
    LOG_LEVEL = Full
    OV_ATTR = _overlaps
    SEPARATE_COLLINEAR_SEGMENTS = No
    LINE -> Tester_21
Tester_21
    BOOL_OP = OR
    TEST_CLAUSE = TEST @Value(_overlaps) > 1
    PASSED -> LengthCalculator
LengthCalculator
    DIM = 2
    LEN_ATTR = _length
    MULT = 1
    -> Tester_22
Tester_22
    BOOL_OP = OR
    TEST_CLAUSE = TEST @Value(_length) > 2
    PASSED -> AttributeCreator_17
AttributeCreator_17
    ATTR_TABLE:
      SET_TO observacao = Sobreposição entre elementos lineares
      SET_TO classe = lote_1_hid_medida_6_2_3
    -> 2DForcer_2
AreaOnAreaOverlayer
    ACCUM_ATTRS_NAME = Use Attributes From One Feature
    CLEANING_TOLERANCE = None
    CONNECT_Z_MODE = First Wins
    DEAGGREGATE_INPUT = Yes
    OVC_ATTR = _overlaps
    AREA -> Tester_18
Tester_18
    BOOL_OP = OR
    TEST_CLAUSE = TEST @Value(_overlaps) > 1
    PASSED -> AreaCalculator_4
AreaCalculator_4
    AREA_ATTR = _area
    AREA_TYPE = Plane Area
    MULT = 1
    -> Tester_19
Tester_19
    BOOL_OP = OR
    TEST_CLAUSE = TEST @Value(_area) > 2
    PASSED -> AttributeCreator_23
AttributeCreator_23
    ATTR_TABLE:
      SET_TO observacao = Sobreposição entre elementos de Massa_Dagua/Trecho_Massa_Dagua
      SET_TO classe = lote_1_hid_medida_6_2_1
    -> 2DForcer_2

Bookmark: hid_medida_4_3_1
fix_2d_10 [off]
    Deaggregator_7_Deaggregated -> GeometryValidator_5
GeometryValidator_5
    ISSUE_ATTR_NAME = _issues
    PRESETS = All
    REPAIR = Yes
    RULES = AREA_ORIENTATION AREA_ORIENTATION]VALID]FME_CONTROLLER_QUERY_FILE]transformers\dependencies\geometryvalidator\AREA_ORIENTATION.fme CONSECUTIVE_IDENTICAL_VERTICES_2D CHECK_Z]YES]FME_CONTROLLER_QUERY_FILE]transformers\dependencies\geometryvalidator\CONSECUTIVE_IDENTICAL_VERTICES_2D.fme MISSING_TEXTURE_COORDINATES  MISSING_VERTEX_NORMALS  NAN_REMOVAL PROCESS_MEASURE]NO]FME_CONTROLLER_QUERY_FILE]transformers\dependencies\geometryvalidator\NAN_REMOVAL.fme NULL_REMOVAL  OGC_SIMPLE_CHECK  OGC_VALID_CHECK OGC_VERSION]V1.2.0]FME_CONTROLLER_QUERY_FILE]transformers\dependencies\geometryvalidator\OGC_VALID_CHECK.fme PLANAR_SURFACE CHECK_AREA]DO_NOT_CHECK_AREA]TOLERANCE_MODE]AUTO]TOLERANCE]0.0]ANGULAR_TOLERANCE_MODE]AUTO]ANGULAR_TOLERANCE]0.0]FME_CONTROLLER_QUERY_FILE]transformers\dependencies\geometryvalidator\PLANAR_SURFACE.fme SELF_INTERSECTING CHECK_HOLE_TOUCHING_POLYGON]No]CONNECT_Z_MODE_SI]FIRST_WINS]FME_CONTROLLER_QUERY_FILE]transformers\dependencies\geometryvalidator\SELF_INTERSECTING.fme SHELL_VALIDATION FLIP_APPEARANCE_MODE]FLIP_APPEARANCES]FME_CONTROLLER_QUERY_FILE]transformers\dependencies\geometryvalidator\SHELL_VALIDATION.fme SOLID_VOID_REPAIR  TYPE_REPAIR CONNECT_Z_MODE]FIRST_WINS]ARC_ENDPOINT_TOLERANCE_MODE]Auto]ARC_ENDPOINT_TOLERANCE]0.0]FME_CONTROLLER_QUERY_FILE]transformers\dependencies\geometryvalidator\TYPE_REPAIR.fme MISMATCHED_DIMENSIONS FORCE_DIMENSION]2D]FME_CONTROLLER_QUERY_FILE]transformers\dependencies\geometryvalidator\MISMATCHED_DIMENSIONS.fme MISSING_MEASURES_AND_ELEVATIONS MISSING_VALUES_MODE]SENTINEL]SENTINEL_VALUE]0]MISSING_MEASURES_MODE]CONTINUOUS]LENGTH_DIMENSION]2D]FME_CONTROLLER_QUERY_FILE]transformers\dependencies\geometryvalidator\MISSING_MEASURES_AND_ELEVATIONS.fme
    SUMMARY = Detailed
    PASSED -> Clipper_6 [CLIPPEE]
    PASSED -> Bufferer_4
Bufferer_4
    ANGLE = 22.5
    CAP_STYLE = Round
    CORNER_STYLE = Round
    MODE = AREA
    OFFSET = -6
    BUFFERED -> GeometryValidator_2
GeometryValidator_2
    ISSUE_ATTR_NAME = _issues
    PRESETS = All
    REPAIR = Yes
    RULES = AREA_ORIENTATION AREA_ORIENTATION]VALID]FME_CONTROLLER_QUERY_FILE]transformers\dependencies\geometryvalidator\AREA_ORIENTATION.fme CONSECUTIVE_IDENTICAL_VERTICES_2D CHECK_Z]YES]FME_CONTROLLER_QUERY_FILE]transformers\dependencies\geometryvalidator\CONSECUTIVE_IDENTICAL_VERTICES_2D.fme MISSING_TEXTURE_COORDINATES  MISSING_VERTEX_NORMALS  NAN_REMOVAL PROCESS_MEASURE]NO]FME_CONTROLLER_QUERY_FILE]transformers\dependencies\geometryvalidator\NAN_REMOVAL.fme NULL_REMOVAL  OGC_SIMPLE_CHECK  OGC_VALID_CHECK OGC_VERSION]V1.2.0]FME_CONTROLLER_QUERY_FILE]transformers\dependencies\geometryvalidator\OGC_VALID_CHECK.fme PLANAR_SURFACE CHECK_AREA]DO_NOT_CHECK_AREA]TOLERANCE_MODE]AUTO]TOLERANCE]0.0]ANGULAR_TOLERANCE_MODE]AUTO]ANGULAR_TOLERANCE]0.0]FME_CONTROLLER_QUERY_FILE]transformers\dependencies\geometryvalidator\PLANAR_SURFACE.fme SELF_INTERSECTING CHECK_HOLE_TOUCHING_POLYGON]No]CONNECT_Z_MODE_SI]FIRST_WINS]FME_CONTROLLER_QUERY_FILE]transformers\dependencies\geometryvalidator\SELF_INTERSECTING.fme SHELL_VALIDATION FLIP_APPEARANCE_MODE]FLIP_APPEARANCES]FME_CONTROLLER_QUERY_FILE]transformers\dependencies\geometryvalidator\SHELL_VALIDATION.fme SOLID_VOID_REPAIR  TYPE_REPAIR CONNECT_Z_MODE]FIRST_WINS]ARC_ENDPOINT_TOLERANCE_MODE]Auto]ARC_ENDPOINT_TOLERANCE]0.0]FME_CONTROLLER_QUERY_FILE]transformers\dependencies\geometryvalidator\TYPE_REPAIR.fme MISMATCHED_DIMENSIONS FORCE_DIMENSION]2D]FME_CONTROLLER_QUERY_FILE]transformers\dependencies\geometryvalidator\MISMATCHED_DIMENSIONS.fme MISSING_MEASURES_AND_ELEVATIONS MISSING_VALUES_MODE]SENTINEL]SENTINEL_VALUE]0]MISSING_MEASURES_MODE]CONTINUOUS]LENGTH_DIMENSION]2D]FME_CONTROLLER_QUERY_FILE]transformers\dependencies\geometryvalidator\MISSING_MEASURES_AND_ELEVATIONS.fme
    SUMMARY = Detailed
    PASSED -> Deaggregator_7
    FAILED -> Deaggregator_7
    REPAIRED -> Deaggregator_7
Deaggregator_7
    ATTR_ACCUM_MODE = Merge List Attributes
    ATTR_CONFLICT_RES = Use List Attribute Values
    CHILD_ID_ATTR = _hierarchy_child_id_list
    COPY_ATTR = Every Node
    EXPLODE_INSTANCES = No
    GEOM_NAME_FIELD = _geometry_name
    ID_ATTR = _hierarchy_id
    ID_SELECTION = ID and Parent ID
    LIST_ATTR_MODE_LOOKUP = LEAN
    MODE = Flatten One Level
    PARENT_ID_ATTR = _hierarchy_parent_id
    PART_NUMBER_FIELD = _part_number
    SPLIT_COMPOSITES = No
    DEAGGREGATED -> GeometryFilter_2
GeometryFilter_2
    BREAK_AGG = No
    GEOM_PORT_NAMES = Area
    AREA -> Bufferer_5
Bufferer_5
    ANGLE = 22.5
    CAP_STYLE = Round
    CORNER_STYLE = Round
    MODE = AREA
    OFFSET = 8
    BUFFERED -> Clipper_6 [CLIPPER]
Clipper_6
    BOUNDARY_CASES = Treat as Inside
    CLEANING_TOLERANCE = None
    CLIPPED_ATTR = _clipped
    CLIP_TYPE = Multiple Clippers
    CREATE_AGGREGATES = No
    LINES_AS_SEGMENTS = No
    MEASURE_TYPE = Continuous
    MISSING_VAL_MODE = Compute
    PRESERVE_CLIPPEE_EXTENTS = No
    VAL_SOURCE = Clippee Only
    OUTSIDE -> Deaggregator_9
Deaggregator_9
    ATTR_ACCUM_MODE = Merge List Attributes
    ATTR_CONFLICT_RES = Use List Attribute Values
    CHILD_ID_ATTR = _hierarchy_child_id_list
    COPY_ATTR = Every Node
    EXPLODE_INSTANCES = No
    GEOM_NAME_FIELD = _geometry_name
    ID_ATTR = _hierarchy_id
    ID_SELECTION = ID and Parent ID
    LIST_ATTR_MODE_LOOKUP = LEAN
    MODE = Flatten One Level
    PARENT_ID_ATTR = _hierarchy_parent_id
    PART_NUMBER_FIELD = _part_number
    SPLIT_COMPOSITES = No
    DEAGGREGATED -> GeometryValidator_4
GeometryValidator_4
    ISSUE_ATTR_NAME = _issues
    PRESETS = All
    REPAIR = Yes
    RULES = AREA_ORIENTATION AREA_ORIENTATION]VALID]FME_CONTROLLER_QUERY_FILE]transformers\dependencies\geometryvalidator\AREA_ORIENTATION.fme CONSECUTIVE_IDENTICAL_VERTICES_2D CHECK_Z]YES]FME_CONTROLLER_QUERY_FILE]transformers\dependencies\geometryvalidator\CONSECUTIVE_IDENTICAL_VERTICES_2D.fme MISSING_TEXTURE_COORDINATES  MISSING_VERTEX_NORMALS  NAN_REMOVAL PROCESS_MEASURE]NO]FME_CONTROLLER_QUERY_FILE]transformers\dependencies\geometryvalidator\NAN_REMOVAL.fme NULL_REMOVAL  OGC_SIMPLE_CHECK  OGC_VALID_CHECK OGC_VERSION]V1.2.0]FME_CONTROLLER_QUERY_FILE]transformers\dependencies\geometryvalidator\OGC_VALID_CHECK.fme PLANAR_SURFACE CHECK_AREA]DO_NOT_CHECK_AREA]TOLERANCE_MODE]AUTO]TOLERANCE]0.0]ANGULAR_TOLERANCE_MODE]AUTO]ANGULAR_TOLERANCE]0.0]FME_CONTROLLER_QUERY_FILE]transformers\dependencies\geometryvalidator\PLANAR_SURFACE.fme SELF_INTERSECTING CHECK_HOLE_TOUCHING_POLYGON]No]CONNECT_Z_MODE_SI]FIRST_WINS]FME_CONTROLLER_QUERY_FILE]transformers\dependencies\geometryvalidator\SELF_INTERSECTING.fme SHELL_VALIDATION FLIP_APPEARANCE_MODE]FLIP_APPEARANCES]FME_CONTROLLER_QUERY_FILE]transformers\dependencies\geometryvalidator\SHELL_VALIDATION.fme SOLID_VOID_REPAIR  TYPE_REPAIR CONNECT_Z_MODE]FIRST_WINS]ARC_ENDPOINT_TOLERANCE_MODE]Auto]ARC_ENDPOINT_TOLERANCE]0.0]FME_CONTROLLER_QUERY_FILE]transformers\dependencies\geometryvalidator\TYPE_REPAIR.fme MISMATCHED_DIMENSIONS FORCE_DIMENSION]2D]FME_CONTROLLER_QUERY_FILE]transformers\dependencies\geometryvalidator\MISMATCHED_DIMENSIONS.fme MISSING_MEASURES_AND_ELEVATIONS MISSING_VALUES_MODE]SENTINEL]SENTINEL_VALUE]0]MISSING_MEASURES_MODE]CONTINUOUS]LENGTH_DIMENSION]2D]FME_CONTROLLER_QUERY_FILE]transformers\dependencies\geometryvalidator\MISSING_MEASURES_AND_ELEVATIONS.fme
    SUMMARY = Detailed
    PASSED -> Deaggregator_10
    FAILED -> Deaggregator_10
    REPAIRED -> Deaggregator_10
Deaggregator_10
    ATTR_ACCUM_MODE = Merge List Attributes
    ATTR_CONFLICT_RES = Use List Attribute Values
    CHILD_ID_ATTR = _hierarchy_child_id_list
    COPY_ATTR = Every Node
    EXPLODE_INSTANCES = No
    GEOM_NAME_FIELD = _geometry_name
    ID_ATTR = _hierarchy_id
    ID_SELECTION = ID and Parent ID
    LIST_ATTR_MODE_LOOKUP = LEAN
    MODE = Flatten One Level
    PARENT_ID_ATTR = _hierarchy_parent_id
    PART_NUMBER_FIELD = _part_number
    SPLIT_COMPOSITES = No
    DEAGGREGATED -> GeometryFilter_4
GeometryFilter_4
    BREAK_AGG = No
    GEOM_PORT_NAMES = Area
    AREA -> AreaCalculator_2
AreaCalculator_2
    AREA_ATTR = _area
    AREA_TYPE = Plane Area
    MULT = 1
    -> Tester_7
Tester_7
    BOOL_OP = OR
    TEST_CLAUSE = TEST @Value(_area) > 500
    PASSED -> AttributeCreator_14
AttributeCreator_14
    ATTR_TABLE:
      SET_TO observacao = Trecho_Massa_Dagua com largura menor que 15 metros
      SET_TO classe = lote_1_hid_medida_4_3_1
    -> 2DForcer_2

Bookmark: hid_medida_4_3_2 / hid_medida_4_3_5 / hid_medida_4_3_6
SpatialFilter_6 [off]
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    FAILED -> AttributeCreator_19
AttributeCreator_19
    ATTR_TABLE:
      SET_TO observacao = Barragem que não possui interseção com Massa_Dagua/Trecho_Massa_Dagua
      SET_TO classe = lote_1_hid_medida_4_3_6
    -> 2DForcer_2
SpatialFilter_7
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> Tester_15
    PASSED -> Tester_16
    FAILED -> Tester_13
    FAILED -> Tester_14
Tester_15
    BOOL_OP = AND
    TEST_CLAUSE:
      TEST @Value(tipomassa) != 10
      TEST @Value(tipotrecho) = ""
    PASSED -> AttributeCreator_21
Tester_16
    BOOL_OP = AND
    TEST_CLAUSE:
      TEST @Value(tipotrecho) != 1
      TEST @Value(tipotrecho) != 10
      TEST @Value(tipomassa) = ""
    PASSED -> AttributeCreator_21
AttributeCreator_21
    ATTR_TABLE:
      SET_TO observacao = Massa_Dagua/Trecho_Massa_Dagua intersecta barragem, não sendo coerente a atributação do seu tipo
      SET_TO classe = lote_1_hid_medida_4_3_5
    -> 2DForcer_2
Tester_13
    BOOL_OP = OR
    TEST_CLAUSE = TEST @Value(tipomassa) = 1
    PASSED -> AttributeCreator_20
Tester_14
    BOOL_OP = OR
    TEST_CLAUSE = TEST @Value(tipotrecho) = 10
    PASSED -> AttributeCreator_20
AttributeCreator_20 [off]
    ATTR_TABLE:
      SET_TO observacao = Represa/Açude sem barragem intersectando
      SET_TO classe = lote_1_hid_medida_4_3_2
    -> 2DForcer_2

Bookmark: hid_medida_6_3_1
GeometryValidator_3
    ISSUE_ATTR_NAME = _issues
    PRESETS = OGC
    REPAIR = Yes
    RULES = OGC_SIMPLE_CHECK  OGC_VALID_CHECK OGC_VERSION]V1.2.0]FME_CONTROLLER_QUERY_FILE]transformers\dependencies\geometryvalidator\OGC_VALID_CHECK.fme
    SUMMARY = Detailed
    PASSED -> CoordinateRounder_3
CoordinateRounder_3
    XPREC = 2
    YPREC = 2
    ZPREC = 1
    ROUNDED -> Intersector
Intersector
    ATTRS_ACCUM_MODE = Use Attributes From One Feature
    CLEANING_TOLERANCE = None
    DEAGGREGATE_INPUT = Yes
    DUPLICATE_Z_NODES = Yes
    GENERATE_LIST_DROP = NO
    MEASURE_TYPE = Continuous
    NODE_NUM_ATTR = _node_number
    OV_ATTR = _overlaps
    PERFORM_SELF_INTERSECTION = No
    SEG_ATTR = _segments
    SEPARATE_COLLINEAR_SEGMENTS = No
    NODE -> CoordinateRounder_2
CoordinateRounder_2
    XPREC = 2
    YPREC = 2
    ZPREC = 1
    ROUNDED -> CoordinateExtractor_2
CoordinateExtractor_2
    IND = 0
    MODE = Specify Coordinate
    Z_ATTR = _z
    -> 2DForcer
2DForcer
    2D -> MeasureRemover
MeasureRemover
    REMOVE_ALL = Yes
    -> GeometryExtractor_2
GeometryExtractor_2
    ATTR = _geometry
    KIND_LONG = FME Binary
    OGCVERSION = 1.2
    OGC_WKT_PRECISION_DISPLAY = 64-bit
    OGEOSMS_URL_PREFIX = http://maps.google.com/?q=
    PREFER_POLYGON_OVER_SURFACE = No
    REMOVE_GEOMETRY = No
    -> DuplicateFilter_2
DuplicateFilter_2
    INPUT_ORDERED_CHOICE = No
    KEYATTR = _geometry
    UNIQUE -> FeatureMerger_2 [REQUESTOR]
    DUPLICATE -> FeatureMerger_2 [SUPPLIER]
FeatureMerger_2
    ATTR_ACCUM_MODE = Merge Supplier
    ATTR_CONFLICT_RES = Use Requestor
    CLEANING_TOLERANCE = None
    CONNECT_Z_MODE = First Wins
    GEOM_TYPE = Build Polygons
    IGNORE_NULLS = No
    JOIN_KEYS = @Value(_geometry) @Value(_geometry) AUTO
    LIST_ATTRS_TO_INCLUDE = _z
    LIST_NAME = ptos
    MERGE_TYPE = Attributes Only
    PROCESS_DUPS = YES
    REJECT_NULL_MISSING_KEYS = No
    SUPPLIERS_FIRST = No
    MERGED -> ListSorter_3
ListSorter_3
    ORDER = Ascending
    SRC_LIST = ptos{}._z
    TYPE = Numeric
    -> AttributeCreator_15
AttributeCreator_15
    ATTR_TABLE = SET_TO z_min = @Value(ptos{0}._z)
    -> ListSorter_4
ListSorter_4
    ORDER = Descending
    SRC_LIST = ptos{}._z
    TYPE = Numeric
    -> AttributeCreator_16
AttributeCreator_16
    ATTR_TABLE:
      SET_TO z_max = @Value(ptos{0}._z)
      SET_TO diff_z = @Evaluate(@Value(z_max)-@Value(z_min))
    -> Tester_6
Tester_6
    BOOL_OP = OR
    TEST_CLAUSE = TEST @Value(diff_z) > 1
    PASSED -> AttributeCreator_3
AttributeCreator_3
    ATTR_TABLE:
      SET_TO observacao = Falta de Snap 3D
      SET_TO classe = lote_1_hid_medida_6_3_1
    -> 2DForcer_2

Bookmark: hid_medida_6_1_1
Deaggregator_4
    ATTR_ACCUM_MODE = Merge List Attributes
    ATTR_CONFLICT_RES = Use List Attribute Values
    CHILD_ID_ATTR = _hierarchy_child_id_list
    COPY_ATTR = Every Node
    EXPLODE_INSTANCES = No
    GEOM_NAME_FIELD = _geometry_name
    ID_ATTR = _hierarchy_id
    ID_SELECTION = ID and Parent ID
    LIST_ATTR_MODE_LOOKUP = LEAN
    MODE = Flatten One Level
    PARENT_ID_ATTR = _hierarchy_parent_id
    PART_NUMBER_FIELD = _part_number
    SPLIT_COMPOSITES = No
    DEAGGREGATED -> AttributeExposer_2
AttributeExposer_2
    ATTR_LIST = fme_feature_type
    -> GeometryFilter
    -> GeometryValidator
GeometryValidator
    ISSUE_ATTR_NAME = _issues
    PRESETS = OGC
    REPAIR = No
    RULES = OGC_SIMPLE_CHECK  OGC_VALID_CHECK OGC_VERSION]V1.2.0]FME_CONTROLLER_QUERY_FILE]transformers\dependencies\geometryvalidator\OGC_VALID_CHECK.fme
    SUMMARY = Detailed
    ISSUE_LOCATIONS -> AttributeValueMapper
AttributeValueMapper
    DEFAULT_VALUE = ERRO
    DIRECTION = Forward (Source To Destination)
    LUT = Self Intersection,Auto interseção,Duplicated Rings,Anéis duplicados,Ring Self Intersection,Auto interseção
    SRC = details
    VAL_ATTR = descricao
    -> Tester_3
Tester_3
    BOOL_OP = OR
    TEST_CLAUSE = TEST @Value(descricao) = ERRO
    PASSED -> Erro_não_filtrado
    FAILED -> Bufferer_3
Erro_não_filtrado: Inspector
GeometryFilter
    BREAK_AGG = No
    GEOM_PORT_NAMES = Point Line Area
    LINE -> SpikeRemover
    AREA -> SpikeRemover
    <UNFILTERED> -> AttributeCreator_10
SpikeRemover
    SPIKEANGLE = 1
    SPIKELENGTH = 0
    REMOVED -> AttributeCreator_9
AttributeCreator_9
    ATTR_TABLE = SET_TO descricao = Spike
    -> Bufferer_3
AttributeCreator_10
    ATTR_TABLE = SET_TO descricao = Tipo de geometria inválido
    -> Bufferer_3
Bufferer_3
    ANGLE = 22.5
    CAP_STYLE = Round
    CORNER_STYLE = Round
    MODE = AREA
    OFFSET = 1
    BUFFERED -> Dissolver
Dissolver
    ACCUM_INPUT_ATTRS = Use Attributes From One Feature
    CLEANING_TOLERANCE = None
    CONNECT_Z_MODE = Ignore
    DEAGGREGATE_INPUT = Yes
    LIST_ATTRS_TO_INCLUDE = descricao
    LIST_NAME = erros
    NO_OVRLP = No
    AREA -> ListDuplicateRemover
ListDuplicateRemover
    SRC_LIST = erros{}.descricao
    -> ListConcatenator
ListConcatenator
    DROP_EMPTY_PARTS = Yes
    LIST_ATTR = erros{}.descricao
    SEP = " | "
    VAL_ATTR = descricao_join
    -> AttributeCreator_2
AttributeCreator_2
    ATTR_TABLE:
      SET_TO classe = lote_1_hid_medida_6_1_1
      SET_TO observacao = Geometria inválida (@Value(descricao_join)) - @Value(fme_feature_type)
    -> 2DForcer_2

Bookmark: hid_medida_8_1_1
Deaggregator
    ATTR_ACCUM_MODE = Merge List Attributes
    ATTR_CONFLICT_RES = Use List Attribute Values
    CHILD_ID_ATTR = _hierarchy_child_id_list
    COPY_ATTR = Every Node
    EXPLODE_INSTANCES = No
    GEOM_NAME_FIELD = _geometry_name
    ID_ATTR = _hierarchy_id
    ID_SELECTION = ID and Parent ID
    LIST_ATTR_MODE_LOOKUP = LEAN
    MODE = Flatten One Level
    PARENT_ID_ATTR = _hierarchy_parent_id
    PART_NUMBER_FIELD = _part_number
    SPLIT_COMPOSITES = No
    DEAGGREGATED -> MeasureRemover_3
MeasureRemover_3
    REMOVE_ALL = Yes
    -> 2DForcer_3
2DForcer_3
    2D -> GeometryExtractor
GeometryExtractor
    ATTR = _geometry
    ELLIPSOID_NAME = WGS84
    GEOHASH_PRECISION_DISPLAY = ~9.3 mm (12 characters)
    ISO6709_FORMAT_CHOICE = Degrees and Decimal Degrees
    ISO6709_MAX_DECIMAL_PLACES = 5
    JSON_MAX_DIGITS = 7
    KIND_LONG = FME Binary
    LETTERING = WGS84
    LEVELS_ATTR = _levels
    MSSQL_FORMAT_CHOICE = Geometry
    OGCVERSION = 1.2
    OGC_WKT_PRECISION_DISPLAY = 64-bit
    OGEOSMS_URL_PREFIX = http://maps.google.com/?q=
    OMIT_NAMESPACES_DISPLAY = No
    PRECISION = 0
    PREFER_POLYGON_OVER_SURFACE = No
    REMOVE_GEOMETRY = No
    -> DuplicateFilter
DuplicateFilter
    INPUT_ORDERED_CHOICE = No
    KEYATTR = _geometry
    DUPLICATE -> AttributeExposer
AttributeExposer
    ATTR_LIST = fme_feature_type
    -> AttributeCreator
AttributeCreator
    ATTR_TABLE:
      SET_TO observacao = Geometria duplicada - @Value(fme_feature_type)
      SET_TO classe = lote_1_hid_medida_8_1_1
    -> 2DForcer_2

Bookmark: hid_medida_8_5_1
CoordinateExtractor_6
    LIST_NAME = _indices
    MODE = All Coordinates
    -> ListExploder_2
ListExploder_2
    ATTR_ACCUM_MODE = Merge List Attributes
    ATTR_CONFLICT_RES = Use List Attribute Values
    INDEX_ATTR = _element_index
    LIST_ATTR = _indices{}
    ELEMENTS -> Tester_26
Tester_26
    BOOL_OP = OR
    TEST_CLAUSE = TEST @Value(z) = 0
    PASSED -> VertexCreator_3
    FAILED -> Tester_27
VertexCreator_3
    MODE_NAME = Replace with Point
    XVAL = @Value(x)
    YVAL = @Value(y)
    -> AttributeCreator_30
AttributeCreator_30
    ATTR_TABLE:
      SET_TO observacao = Vertice com cota 0, verificar se correto
      SET_TO classe = lote_1_hid_medida_8_5_1
    -> 2DForcer_2
Tester_27
    BOOL_OP = OR
    TEST_CLAUSE = TEST @Value(z) > 1250
    PASSED -> VertexCreator_4
VertexCreator_4
    MODE_NAME = Replace with Point
    XVAL = @Value(x)
    YVAL = @Value(y)
    -> AttributeCreator_31
AttributeCreator_31
    ATTR_TABLE:
      SET_TO observacao = Cota com valor extremo, verificar se correto
      SET_TO classe = lote_1_hid_medida_8_5_2
    -> 2DForcer_2

Bookmark: Vetores de altimetria
REL_Curva_Nivel_L (reader ESRISHAPE_2) [off]
    attributes: COTA double, depressao short, indice short
    -> fix_2d_curva [2DForcer_3_Input]

Bookmark: Shapefile de saída
2DForcer_2
    2D -> MeasureRemover_2
MeasureRemover_2
    REMOVE_ALL = Yes
    -> AttributeKeeper
AttributeKeeper
    KEEP_ATTRS = observacao,classe
    -> Deaggregator_2
Deaggregator_2
    ATTR_ACCUM_MODE = Merge List Attributes
    ATTR_CONFLICT_RES = Use List Attribute Values
    CHILD_ID_ATTR = _hierarchy_child_id_list
    COPY_ATTR = Every Node
    EXPLODE_INSTANCES = No
    GEOM_NAME_FIELD = _geometry_name
    ID_ATTR = _hierarchy_id
    ID_SELECTION = ID and Parent ID
    LIST_ATTR_MODE_LOOKUP = LEAN
    MODE = Flatten One Level
    PARENT_ID_ATTR = _hierarchy_parent_id
    PART_NUMBER_FIELD = _part_number
    SPLIT_COMPOSITES = No
    DEAGGREGATED -> GeometryValidator_7
GeometryValidator_7
    ISSUE_ATTR_NAME = _issues
    PRESETS = All
    REPAIR = Yes
    RULES = AREA_ORIENTATION AREA_ORIENTATION]VALID]FME_CONTROLLER_QUERY_FILE]transformers\dependencies\geometryvalidator\AREA_ORIENTATION.fme CONSECUTIVE_IDENTICAL_VERTICES_2D CHECK_Z]YES]FME_CONTROLLER_QUERY_FILE]transformers\dependencies\geometryvalidator\CONSECUTIVE_IDENTICAL_VERTICES_2D.fme MISSING_TEXTURE_COORDINATES  MISSING_VERTEX_NORMALS  NAN_REMOVAL PROCESS_MEASURE]NO]FME_CONTROLLER_QUERY_FILE]transformers\dependencies\geometryvalidator\NAN_REMOVAL.fme NULL_REMOVAL  OGC_SIMPLE_CHECK  OGC_VALID_CHECK OGC_VERSION]V1.2.0]FME_CONTROLLER_QUERY_FILE]transformers\dependencies\geometryvalidator\OGC_VALID_CHECK.fme PLANAR_SURFACE CHECK_AREA]DO_NOT_CHECK_AREA]TOLERANCE_MODE]AUTO]TOLERANCE]0.0]ANGULAR_TOLERANCE_MODE]AUTO]ANGULAR_TOLERANCE]0.0]FME_CONTROLLER_QUERY_FILE]transformers\dependencies\geometryvalidator\PLANAR_SURFACE.fme SELF_INTERSECTING CHECK_HOLE_TOUCHING_POLYGON]No]CONNECT_Z_MODE_SI]FIRST_WINS]FME_CONTROLLER_QUERY_FILE]transformers\dependencies\geometryvalidator\SELF_INTERSECTING.fme SHELL_VALIDATION FLIP_APPEARANCE_MODE]FLIP_APPEARANCES]FME_CONTROLLER_QUERY_FILE]transformers\dependencies\geometryvalidator\SHELL_VALIDATION.fme SOLID_VOID_REPAIR  TYPE_REPAIR CONNECT_Z_MODE]FIRST_WINS]ARC_ENDPOINT_TOLERANCE_MODE]Auto]ARC_ENDPOINT_TOLERANCE]0.0]FME_CONTROLLER_QUERY_FILE]transformers\dependencies\geometryvalidator\TYPE_REPAIR.fme MISMATCHED_DIMENSIONS FORCE_DIMENSION]2D]FME_CONTROLLER_QUERY_FILE]transformers\dependencies\geometryvalidator\MISMATCHED_DIMENSIONS.fme MISSING_MEASURES_AND_ELEVATIONS MISSING_VALUES_MODE]SENTINEL]SENTINEL_VALUE]0]MISSING_MEASURES_MODE]CONTINUOUS]LENGTH_DIMENSION]2D]FME_CONTROLLER_QUERY_FILE]transformers\dependencies\geometryvalidator\MISSING_MEASURES_AND_ELEVATIONS.fme
    SUMMARY = Detailed
    PASSED -> Deaggregator_6
    FAILED -> Deaggregator_6
    REPAIRED -> Deaggregator_6
Deaggregator_6
    ATTR_ACCUM_MODE = Merge List Attributes
    ATTR_CONFLICT_RES = Use List Attribute Values
    CHILD_ID_ATTR = _hierarchy_child_id_list
    COPY_ATTR = Every Node
    EXPLODE_INSTANCES = No
    GEOM_NAME_FIELD = _geometry_name
    ID_ATTR = _hierarchy_id
    ID_SELECTION = ID and Parent ID
    LIST_ATTR_MODE_LOOKUP = LEAN
    MODE = Flatten One Level
    PARENT_ID_ATTR = _hierarchy_parent_id
    PART_NUMBER_FIELD = _part_number
    SPLIT_COMPOSITES = No
    DEAGGREGATED -> Bufferer
Bufferer
    ANGLE = 22.5
    CAP_STYLE = Round
    CORNER_STYLE = Round
    MODE = AREA
    OFFSET = 2
    BUFFERED -> HID_Trecho_Massa_Dagua_A (writer ESRISHAPE_3)
HID_Trecho_Massa_Dagua_A (writer ESRISHAPE_3)
    attributes: observacao char(254)

FME custom transformer fix_2d

2DForcer_3_Input (input)
    -> 2DForcer_3
2DForcer_3
    2D -> MeasureRemover_4
MeasureRemover_4
    REMOVE_ALL = Yes
    -> Deaggregator_7
Deaggregator_7
    ATTR_ACCUM_MODE = Merge List Attributes
    ATTR_CONFLICT_RES = Use List Attribute Values
    CHILD_ID_ATTR = _hierarchy_child_id_list
    COPY_ATTR = Every Node
    EXPLODE_INSTANCES = No
    GEOM_NAME_FIELD = _geometry_name
    ID_ATTR = _hierarchy_id
    ID_SELECTION = ID and Parent ID
    LIST_ATTR_MODE_LOOKUP = LEAN
    MODE = Flatten One Level
    PARENT_ID_ATTR = _hierarchy_parent_id
    PART_NUMBER_FIELD = _part_number
    SPLIT_COMPOSITES = No
    DEAGGREGATED -> Deaggregator_7_Deaggregated (output)
Deaggregator_7_Deaggregated (output)
